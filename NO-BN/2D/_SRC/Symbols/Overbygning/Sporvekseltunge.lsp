;
; Sporvekseltunge.lsp
;
(defun C:SPORVEKSELTUNGE ()
	(Tounge "NO-BN-2D-JBTOB-SPORVEKSELTUNGE-09-R190" "0.6490,0.75" "H" 9.8740)
	(Tounge "NO-BN-2D-JBTOB-SPORVEKSELTUNGE-09-R300" "0.8030,0.75" "H" 15.8120)
	(Tounge "NO-BN-2D-JBTOB-SPORVEKSELTUNGE-11.66-R500" "0.8030,0.75" "H" 20.0)
	(Tounge "NO-BN-2D-JBTOB-SPORVEKSELTUNGE-12-R500" "0.8030,0.75" "H" 20.0)
	(Tounge "NO-BN-2D-JBTOB-SPORVEKSELTUNGE-14-R760" "0.8030,0.75" "H" 26.305)
	(Tounge "NO-BN-2D-JBTOB-SPORVEKSELTUNGE-15-R760" "0.8030,0.75" "H" 24.502)
	(Tounge "NO-BN-2D-JBTOB-SPORVEKSELTUNGE-18.4-R1200" "0.8030,0.75" "H" 32.026)
	(Tounge "NO-BN-2D-JBTOB-SPORVEKSELTUNGE-26.1-R2500" "0.8030,0.75" "H" 47.306)
	(Tounge "NO-BN-2D-JBTOB-SPORVEKSELTUNGE-09-R190" "0.6490,-0.75" "V" 9.8740)
	(Tounge "NO-BN-2D-JBTOB-SPORVEKSELTUNGE-09-R300" "0.8030,-0.75" "V" 15.8120)
	(Tounge "NO-BN-2D-JBTOB-SPORVEKSELTUNGE-11.66-R500" "0.8030,-0.75" "V" 20.0)
	(Tounge "NO-BN-2D-JBTOB-SPORVEKSELTUNGE-12-R500" "0.8030,-0.75" "V" 20.0)
	(Tounge "NO-BN-2D-JBTOB-SPORVEKSELTUNGE-14-R760" "0.8030,-0.75" "V" 26.305)
	(Tounge "NO-BN-2D-JBTOB-SPORVEKSELTUNGE-15-R760" "0.8030,-0.75" "V" 24.502)
	(Tounge "NO-BN-2D-JBTOB-SPORVEKSELTUNGE-18.4-R1200" "0.8030,-0.75" "V" 32.026)
	(Tounge "NO-BN-2D-JBTOB-SPORVEKSELTUNGE-26.1-R2500" "0.8030,-0.75" "V" 47.306)
)

(defun Tounge (blockName toungePos side toungeLen / )
	(setvar "ATTDIA" 0)
	(setvar "ATTREQ" 0)
    (command
		"._COLOR" "ByBlock"
		"._LAYER" "Set" "0" ""
		"._LINE" toungePos (strcat "@" (rtos toungeLen) ",0") ""
		"._LAYER" "Set" "0" ""
	)
	(newBlock (strcat blockName "-" side))
)
