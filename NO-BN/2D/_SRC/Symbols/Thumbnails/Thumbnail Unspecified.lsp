;=========================================================================================================================
;
; Thumbnail Unspecified.lsp
;
; Copyright Railcomplete AS / NO916118503, 2015-2021. All rights reserved.
; RailCOMPLETE (R) and the RailCOMPLETE logo are registered trademarks owned by Railcomplete AS.
;
; Change log:
; 2021-02-10 CLFEY Release 2021.a
;
;=========================================================================================================================

; Thumbnail for unspecified object selection (in use for abstract objects, or when 2D symbol has not yet been produced)

(defun C:THUMBNAIL-UNSPECIFIED ( / )
	(THUMBNAIL-UNSPECIFIED)
)



(defun THUMBNAIL-UNSPECIFIED (/ blockName x y) 
	; A rectangle, a circle and a triangle - to be used as proxy symbols for anything that lacks a suitable symbol.
	(setq blockName (strcat "NO-BN-2D-JBTFE-THUMBNAIL-UNSPECIFIED"))
	(command 
		_RECTANGLE_ "0,-3" "4,1"
		_CIRCLE_ "-1,-1" "3"
		_POLYGON_ "3" _specifyEdgeOfPolygon_ "-3,0" "3,0"
	)
	(CreateSchematicBlockFromCurrentGraphics blockName)
)
