;
; Controller.lsp
;
(defun C:CONTROLLER ()
	(CONTROLLER)
)



(defun CONTROLLER (/ blockName)
	(setq
		blockName "NO-BN-2D-JBTFE-KONTROLLER"
	)
	(command
		"._LINE" "0,-0.875" "-0.875,0" ""
		"._LINE" "0,0.875" "-1.0607,-0.1857" ""
		"._CIRCLE" "-1.2676,-0.3926" 0.2927
		"._MIRROR" "ALL" "" "0,0" "0,1" "N"
		"._LINE" "0,-2.125" "0,1.075" ""
	)
	(newBlock blockName)
	blockName
)



; INFO 2019-05-07 CLFEY:Not in use:
(defun CONTROLLER_DETAILED (/ blockName)
	(setq 
		blockName "NO-BN-2D-JBTFE-KONTROLLER-DETALJERT"
	)
	(command "._LINE" "0,0" "-0.064,0" "-0.064,0.173" ""
		"._PLINE" "-0.102,0.236" "ARC" "CE" "-0.064,0.216" (list (- 0.047) 0.256) ""
		"._CIRCLE" "-0.064,0.216" "0.02"
		"._LINE" "-0.102,0.236" "-0.137,0.33" "-0.081,0.35" "-0.047,0.256" ""
		"._LINE" "-0.021,0.216" "0,0.216" ""
		"._LINE" "-0.022,0.228" "-0.022,1.289" ""
		"._LINE" "0,1.289" "-0.045,1.289" "-0.045,1.426" ""
		"._PLINE" "0,1.471" "ARC" "CE" "0,1.426" (list (- 0.045) 1.426) ""
		"._PLINE" "0,1.446" "ARC" "CE" "0,1.426" (list 0 1.406) ""
		"._LINE" "-0.045,1.384" "-0.065,1.349" "-0.099,1.369" "-0.061,1.435" "-0.045,1.426" ""
		"._LINE" "-0.091,1.364" "-0.313,0.975" ""
		"._LINE" "-0.073,1.354" "-0.296,0.965" ""
		"._LINE" "-0.095,0.345" "-0.266,0.815" ""
		"._LINE" "-0.123,0.335" "-0.294,0.805" ""
		"._LINE" "-0.286,0.914" "-0.252,0.82" "-0.308,0.8" "-0.342,0.894" ""
		"._PLINE" "-0.286,0.914" "ARC" "CE" "-0.325,0.933" (list (- 0.342) 0.894) ""
		"._CIRCLE" "-0.325,0.933" "0.011"
		"._LINE" "-0.34,0.887" "-0.415,0.756" ""
		"._LINE" "-0.354,0.902" "-0.432,0.766" ""
		"._PLINE" "-0.398,0.744" "ARC" "CE" "-0.515,0.601" (list (- 0.451) 0.774) ""
		"._CIRCLE" "-0.515,0.601" "0.177"
		"._LINE" "-0.398,0.744" "-0.403,0.738" ""
		"._LINE" "-0.451,0.774" "-0.453,0.766" ""
		"._MIRROR" "ALL" "" "0,0" "0,1" "N"
	)
	(new Block blockName)
	blockName
)
