(defun drawMKs (pole / rMKsradius topFKs lanternMKs)
	(setq
		r (getSradius)
		MKsradius (getMKsradius)
		topFKs (list (- pole (* 4 r)) (- r))
		lanternMKs (list (- pole r) MKsradius)
	)
	(command "._CIRCLE" lanternMKs MKsradius)
	(princ)
)
